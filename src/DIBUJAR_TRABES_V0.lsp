;; ==============================================================================
;; DIBUJAR_TRABE_V13.LSP
;; BASE: V12.
;; CORRECCION FINAL GANCHOS:
;;  - Se calculan respecto al CENTRO DE LA VARILLA (no del filete).
;;  - Se aplica un offset de 1.1 * RadioVarilla desde el punto tangente.
;;  - Esto garantiza que el gancho nazca fuera del volumen visual de la dona.
;; ==============================================================================

(defun ocmema:beam:const-armar-from-anl (anlPath / *error* file dir filename tempFile wsh cmd fp line 
                            coordList YD ZB startX endX l_total_cm l_total_m h_cm b_cm 
                            h_draw rectLen ptOrigin xOrigin yOrigin oldOsnap p1 p2 
                            idx numNodes hasAxis axisName posType drawX extraX drawRed supportNodes
                            pAxisBot pAxisTop centerCircle axisXList dimXList axisCenter
                            dataMode strList valX nodeID
                            tokenList i len token currentDist xOffsetGlobal 
                            globalSteelList
                            valAstTop valAstBot maxDemBot maxDemTop 
                            ;; Variables Trabe
                            fc_val asMinFormula asBaseTop asBaseBot strVarBaseTop strVarBaseBot
                            numBaseTop numBaseBot areaBarBot areaBarTop qtyRecBot qtyRecTop
                            ans numBars strVar row zoneStart zoneEnd req d strVarBast 
                            yBot yTop xDrawStart xDrawEnd 
                            pts pTail pCrank pJoin foundBot j
                            nID nX_m maxDistFound
                            posTypeSteel valAst cleanLine
                            redondear-al-5 get-closest-axis dibujar-leader-blindado
                            obtener-x-interpolada procesar-zonas-v27 calc-puntos-v27
                            obtener-area-varilla obtener-diametro-real
                            x_ini_inf x_fin_inf axis_near_start axis_near_end
                            x_baston_ini x_baston_fin
                            dist_izq dist_der scan_x found
                            p_start p_end p_crank_start p_crank_end
                            usar_minimo len_final_izq len_final_der
                            old_dimasz old_dimclrd old_dimtxt old_dimclrt old_dimscale
                            list_zonas_inf list_zonas_sup zona
                            memberOffsetList mIndex pos k
                            areaBastOne qtyBastRec numBast deficit
                            bastonesInfList bastonesSupList
                            strVarBastGlobal areaBastGlobal d_baston_cm tolX
                            rawBast normBast
                            ptsCorrInf ptsCorrSup zonesInf zonesSup z iStart iEnd
                            borders xLstar xRstar xL xR ok Ld_m
                            numZonesEstribos lenZoneEst s_estribo qtyEstribos limitEstribos
                            yTextEstribos txtEstribo pTextEst d_eff
                            addCamber numCamber locCamber xCamber pCamber yCamber strCamber
                            ptSectionOrigin xSec ySec h_losa typeLosa alignLosa capaCompresion
                            rec_draw b_draw h_draw_sec p1_losa p2_losa p3_losa p4_losa
                            draw-stirrup-hooks draw-break-line
                            critBastInf critBastSup
                            process-layer-steel get-critical-bast
                            widthName
                            radFillet pH1 pH2 rBarTop xStirrupLeft yStirrupTop
                            offsetHookFactor centerBarX centerBarY
                            projectItem projectPlant projectPoints axisPairsX axisPairsY
                            axisTolDraw autoAxisFamily autoAxisEnabled autoAxisName
                            hasProjectAxes useModel3dAxis isSupportNode
                            projectPointNodeMap mappedPoint
                            )

  (princ "\nOCMEMA DBG: running DIBUJAR_TRABES_V0.lsp from repo src (DIBUJAR_TRABE_SIMPLE)")
  (vl-load-com)
  (setq ocmema--default-project-dir "C:\\Users\\edgar\\OneDrive - ITESO\\OCMEMA_IE\\01. PROYECTOS\\")

  ;; --- 1. FUNCIONES AUXILIARES ---

  (defun redondear-al-5 (val) (* 0.05 (fix (+ (/ val 0.05) 0.5))))

  (defun get-closest-axis (x_pt axis_list / min_dist best_axis axis dist)
    (setq min_dist 100000.0 best_axis nil)
    (foreach axis axis_list
      (setq dist (abs (- x_pt axis)))
      (if (< dist min_dist) (progn (setq min_dist dist) (setq best_axis axis)))
    )
    best_axis
  )

  (defun ocmema--support-ids-from-line (rawLine / toks out i cur nxt tmp)
    (setq out '())
    (if (and rawLine (> (strlen rawLine) 0))
      (progn
        (setq toks (read (strcat "(" (vl-string-translate "." " " (clean-string rawLine)) ")")))
        (setq i 0)
        (while (< i (length toks))
          (setq cur (nth i toks))
          (cond
            ((numberp cur)
              (if (and (< (+ i 2) (length toks))
                       (eq (nth (1+ i) toks) 'TO)
                       (numberp (nth (+ i 2) toks)))
                (progn
                  (setq nxt (nth (+ i 2) toks))
                  (if (> cur nxt)
                    (progn (setq tmp cur) (setq cur nxt) (setq nxt tmp))
                  )
                  (while (<= cur nxt)
                    (if (not (member cur out))
                      (setq out (append out (list cur)))
                    )
                    (setq cur (1+ cur))
                  )
                  (setq i (+ i 3))
                )
                (progn
                  (if (not (member cur out))
                    (setq out (append out (list cur)))
                  )
                  (setq i (1+ i))
                )
              )
            )
            (T (setq i (length toks)))
          )
        )
      )
    )
    out
  )

  (defun obtener-x-interpolada (x1 y1 x2 y2 target)
    (if (equal y2 y1 0.0000001) x1 (+ x1 (* (- target y1) (/ (- x2 x1) (- y2 y1)))))
  )

  (defun obtener-area-varilla (numVar / area)
     (cond ((= numVar "2.5") 0.49) ((= numVar "3") 0.71) ((= numVar "4") 1.27)
           ((= numVar "5") 1.98) ((= numVar "6") 2.85) ((= numVar "8") 5.07)
           ((= numVar "10") 7.92) ((= numVar "12") 11.40) (t 0.0))
  )
  
  (defun obtener-diametro-real (numVar / d)
     (cond ((= numVar "2.5") 0.79) ((= numVar "3") 0.95) ((= numVar "4") 1.27)
           ((= numVar "5") 1.59) ((= numVar "6") 1.91) ((= numVar "8") 2.54)
           ((= numVar "10") 3.18) ((= numVar "12") 3.81) (t 1.0))
  )

  (defun ocmema--valid-bar? (s)
     (member s '("2.5" "3" "4" "5" "6" "8" "10" "12"))
  )

  (defun ocmema:ask-base-varilla (prompt / raw n tries)
     (setq tries 0 n nil)
     (while (< tries 2)
       (setq raw (getstring prompt))
       (princ (strcat "\nOCMEMA DBG: baseVar input=" (vl-princ-to-string raw) " type=" (vl-princ-to-string (type raw))))
       (if (and (null raw) (= tries 0)) (setq raw ""))
       (if (= (type raw) 'STR)
         (progn
           (setq raw (vl-string-translate "#" "" (vl-string-trim " \t" raw)))
           (if (= raw "") (setq n nil) (setq n raw))
         )
         (if (numberp raw) (setq n (itoa (fix raw))))
       )
       (if (and n (ocmema--valid-bar? n))
         (setq tries 99)
         (progn
           (princ "\nOCMEMA WARN: varilla base invalida, usando default 3")
           (setq n "3")
           (setq tries 99)
         )
       )
       (setq tries (1+ tries))
     )
     n
  )

  (defun ocmema:ask-baston-calibre (/ raw n tries)
     (setq tries 0)
     (while (< tries 2)
       (princ "\nOCMEMA DBG: pidiendo calibre baston (fn=ocmema:ask-baston-calibre)")
       (setq raw (vl-catch-all-apply '(lambda () (getstring T "\nCalibre baston (3/4/5/6/8) <3>: "))))
       (if (vl-catch-all-error-p raw)
         (progn
           (princ (strcat "\nOCMEMA WARN: error leyendo calibre baston: " (vl-catch-all-error-message raw)))
           (setq raw "")
         )
       )
       (princ (strcat "\nOCMEMA DBG: calibre input raw=" (vl-princ-to-string raw) " type=" (vl-princ-to-string (type raw))))
       (if (or (null raw) (= raw "")) (setq n "3"))
       (if (and (not n) (numberp raw)) (setq n (itoa (fix raw))))
       (if (and (not n) (= (type raw) 'STR))
         (progn
           (setq raw (vl-string-translate "#" "" (vl-string-trim " \t" raw)))
           (if (member raw '("3" "4" "5" "6" "8")) (setq n raw))
         )
       )
       (if (member n '("3" "4" "5" "6" "8")) (progn (setq tries 99)) (progn (princ "\nOCMEMA WARN: calibre invalido, usando default 3") (setq n "3") (setq tries 99)))
       (setq tries (1+ tries))
     )
     n
  )

  (defun ocmema--norm-baston (s / t)
     (cond
       ((null s) nil)
       ((= (type s) 'STR) (setq t s))
       ((numberp s)
         (setq t (rtos s 2 2))
         (setq t (vl-string-right-trim "0" t))
         (if (and (> (strlen t) 0) (= (substr t (strlen t) 1) "."))
           (setq t (substr t 1 (1- (strlen t))))
         )
       )
       (t (setq t (vl-princ-to-string s)))
     )
     (if t
       (progn
         (setq t (vl-string-trim " \t" t))
         (setq t (vl-string-translate "#" "" t))
         (if (= t "") nil t)
       )
       nil
     )
  )

  (defun ocmema--build-pts (steelList idx x_origin_draw / base pts pt vx vy)
    (setq base (+ x_origin_draw 0.5))
    (setq pts '())
    (foreach pt steelList
      (setq vx (car pt)) (setq vy (nth idx pt))
      (if (and (numberp vx) (numberp vy))
        (setq pts (append pts (list (list (+ base vx) vy))))
        (princ (strcat "\nOCMEMA WARN: steel point with nil values skipped: " (vl-princ-to-string pt)))
      )
    )
    (vl-sort pts '(lambda (a b) (< (car a) (car b))))
  )

  (defun ocmema--build-pts-dist (steelList idx / pts pt dist_m asreq)
    (setq pts '())
    (foreach pt steelList
      (setq dist_m (car pt)) (setq asreq (nth idx pt))
      (if (and (numberp dist_m) (numberp asreq))
        (setq pts (append pts (list (list (* dist_m 100.0) asreq))))
        (princ (strcat "\nOCMEMA WARN: steel point with nil values skipped: " (vl-princ-to-string pt)))
      )
    )
    (vl-sort pts '(lambda (a b) (< (car a) (car b))))
  )

  (defun ocmema--alist-get-local (key alst / out target item)
    (setq out nil)
    (setq target (strcase (vl-princ-to-string key)))
    (if (listp alst)
      (foreach item alst
        (if (and (listp item)
                 (= (strcase (vl-princ-to-string (car item))) target))
          (setq out (cdr item))
        )
      )
    )
    out
  )

  (defun ocmema--normalize-name-local (s)
    (strcase (vl-string-trim " \t" (if s (vl-princ-to-string s) "")))
  )

  (defun ocmema--find-project-item-local (bucket itemName / proj items norm found item)
    (setq found nil)
    (setq proj (if (and (boundp 'ocmema:*project*) ocmema:*project*) ocmema:*project* nil))
    (setq items (if proj (ocmema--alist-get-local bucket proj) nil))
    (setq norm (ocmema--normalize-name-local itemName))
    (if (listp items)
      (foreach item items
        (if (= (ocmema--normalize-name-local (ocmema--alist-get-local "name" item)) norm)
          (setq found item)
        )
      )
    )
    found
  )

  (defun ocmema--find-plant-local (plantIdx / proj plants found plant)
    (setq found nil)
    (setq proj (if (and (boundp 'ocmema:*project*) ocmema:*project*) ocmema:*project* nil))
    (setq plants (if proj (ocmema--alist-get-local "plants" proj) nil))
    (if (listp plants)
      (foreach plant plants
        (if (= (ocmema--alist-get-local "idx" plant) plantIdx)
          (setq found plant)
        )
      )
    )
    found
  )

  (defun ocmema--meta-model3d-p (meta)
    (and (= (type meta) 'STR)
         (wcmatch (strcase meta) "*SOURCE=MODELO3D*"))
  )

  (defun ocmema--project-draw-unit-factor-local (/ proj u)
    (setq proj (if (and (boundp 'ocmema:*project*) ocmema:*project*) ocmema:*project* nil))
    (setq u (if proj (ocmema--alist-get-local "draw_units" proj) nil))
    (if (not u) (setq u (if proj (ocmema--alist-get-local "units" proj) nil)))
    (setq u (strcase (if u (vl-princ-to-string u) "M")))
    (cond
      ((= u "CM") 1.0)
      ((= u "C") 1.0)
      ((= u "MM") 0.1)
      (T 100.0)
    )
  )

  (defun ocmema--project-scale-local (/ proj sc)
    (setq proj (if (and (boundp 'ocmema:*project*) ocmema:*project*) ocmema:*project* nil))
    (setq sc (if proj (ocmema--alist-get-local "draw_scale_factor" proj) nil))
    (if (not (numberp sc)) (setq sc (if proj (ocmema--alist-get-local "scale" proj) nil)))
    (if (not (numberp sc)) (setq sc 1.0))
    (if (<= sc 0.0) (setq sc 1.0))
    sc
  )

  (defun ocmema--axis-tol-draw (/ sc uf)
    (setq sc (ocmema--project-scale-local))
    (setq uf (ocmema--project-draw-unit-factor-local))
    (/ (* 2.0 sc) uf)
  )

  (defun ocmema--point-x (pt)
    (if (and (listp pt) (numberp (car pt))) (car pt) nil)
  )

  (defun ocmema--point-y (pt)
    (if (and (listp pt) (numberp (cadr pt))) (cadr pt) nil)
  )

  (defun ocmema--axis-family-from-points (pts tol / p0 pN dx dy)
    (setq p0 (if (and (listp pts) (> (length pts) 0)) (car pts) nil))
    (setq pN (if (and (listp pts) (> (length pts) 1)) (last pts) nil))
    (if (and (listp pN) (= (length pN) 1)) (setq pN (car pN)))
    (if (and p0 pN
             (numberp (ocmema--point-x p0)) (numberp (ocmema--point-y p0))
             (numberp (ocmema--point-x pN)) (numberp (ocmema--point-y pN)))
      (progn
        (setq dx (abs (- (ocmema--point-x pN) (ocmema--point-x p0))))
        (setq dy (abs (- (ocmema--point-y pN) (ocmema--point-y p0))))
        (cond
          ((<= dy tol) "X")
          ((<= dx tol) "Y")
          (T nil)
        )
      )
      nil
    )
  )

  (defun ocmema--axis-name-from-coord (coord axisPairs tol / out pair axisVal)
    (setq out nil)
    (if (and (numberp coord) (listp axisPairs))
      (foreach pair axisPairs
        (setq axisVal (cdr pair))
        (if (and (numberp axisVal) (<= (abs (- coord axisVal)) tol))
          (setq out (car pair))
        )
      )
    )
    out
  )

  (defun ocmema--auto-axis-name-for-index (idx pts family axisPairsX axisPairsY tol / pt coord)
    (setq pt (if (and (listp pts) (>= idx 0) (< idx (length pts))) (nth idx pts) nil))
    (cond
      ((or (not pt) (not family)) nil)
      ((= family "X")
        (setq coord (ocmema--point-x pt))
        (ocmema--axis-name-from-coord coord axisPairsX tol)
      )
      ((= family "Y")
        (setq coord (ocmema--point-y pt))
        (ocmema--axis-name-from-coord coord axisPairsY tol)
      )
      (T nil)
    )
  )

  (defun ocmema--draw-delta-to-cm (delta / sc)
    (setq sc (ocmema--project-scale-local))
    (/ (* (abs delta) (ocmema--project-draw-unit-factor-local)) sc)
  )

  (defun ocmema--plant-match-score (plant pts family tol / axes score pt coord)
    (setq score 0)
    (setq axes (if (= family "X")
                 (ocmema--alist-get-local "x_axes" plant)
                 (ocmema--alist-get-local "y_axes" plant)))
    (if (listp pts)
      (foreach pt pts
        (setq coord (if (= family "X") (ocmema--point-x pt) (ocmema--point-y pt)))
        (if (ocmema--axis-name-from-coord coord axes tol)
          (setq score (1+ score))
        )
      )
    )
    score
  )

  (defun ocmema--best-plant-local (pts family tol / proj plants best bestScore score plant)
    (setq best nil)
    (setq bestScore -1)
    (setq proj (if (and (boundp 'ocmema:*project*) ocmema:*project*) ocmema:*project* nil))
    (setq plants (if proj (ocmema--alist-get-local "plants" proj) nil))
    (if (listp plants)
      (foreach plant plants
        (setq score (ocmema--plant-match-score plant pts family tol))
        (if (> score bestScore)
          (progn
            (setq best plant)
            (setq bestScore score)
          )
        )
      )
    )
    (if (> bestScore 0) best nil)
  )

  (defun ocmema--map-points-to-node-indexes (pts family coordList startX / numPts numNodes out baseCoord prevIdx j remaining searchEnd bestIdx bestErr i targetDist nodeDist)
    (cond
      ((or (not (listp pts)) (< (length pts) 2)) nil)
      ((> (length pts) (length coordList)) 'ERR_MORE_POINTS)
      (T
        (setq numPts (length pts))
        (setq numNodes (length coordList))
        (setq out (list (cons 0 0)))
        (setq baseCoord (if (= family "X") (ocmema--point-x (car pts)) (ocmema--point-y (car pts))))
        (setq prevIdx 0)
        (setq j 1)
        (while (< j (1- numPts))
          (setq remaining (- numPts j))
          (setq searchEnd (- numNodes remaining))
          (setq targetDist (ocmema--draw-delta-to-cm (- (if (= family "X")
                                                         (ocmema--point-x (nth j pts))
                                                         (ocmema--point-y (nth j pts)))
                                                      baseCoord)))
          (setq bestIdx nil)
          (setq bestErr nil)
          (setq i (1+ prevIdx))
          (while (<= i searchEnd)
            (setq nodeDist (- (cadr (nth i coordList)) startX))
            (if (or (null bestErr) (< (abs (- nodeDist targetDist)) bestErr))
              (progn
                (setq bestErr (abs (- nodeDist targetDist)))
                (setq bestIdx i)
              )
            )
            (setq i (1+ i))
          )
          (if (null bestIdx)
            (setq j numPts)
            (progn
              (setq out (append out (list (cons bestIdx j))))
              (setq prevIdx bestIdx)
              (setq j (1+ j))
            )
          )
        )
        (if (= (length out) (1- numPts))
          (setq out (append out (list (cons (1- numNodes) (1- numPts)))))
        )
        out
      )
    )
  )

  (defun ocmema--mapped-point-for-node-index (nodeIdx mapping pts / pair pairTmp)
    (setq pair nil)
    (if (listp mapping)
      (foreach pairTmp mapping
        (if (= (car pairTmp) nodeIdx)
          (setq pair pairTmp)
        )
      )
    )
    (if (and pair (listp pts) (>= (cdr pair) 0) (< (cdr pair) (length pts)))
      (nth (cdr pair) pts)
      nil
    )
  )

  (defun ocmema:dist->x (dist_cm x_support0 scaleX)
    (+ x_support0 (* dist_cm scaleX))
  )

  (defun ocmema--floor5cm (v) (* 5.0 (fix (/ v 5.0))))
  (defun ocmema--ceil5cm (v) (* 5.0 (fix (+ (/ v 5.0) 0.9999))))

  (defun ocmema--interp-borders-dist (pts needFlags iStart iEnd asLong d_cm face L_total_cm / n x0 y0 x1 y1 m b xStar inSeg distLstar distRstar Ld_cm distL distR ok reason addR_cm)
    (setq n (length pts) ok T reason nil addR_cm 0.0)
    (if (or (not (numberp d_cm)) (<= d_cm 0.0)) (setq ok nil reason "no_d"))
    (if (and ok (or (< iStart 0) (< iEnd 0) (>= iStart n) (>= iEnd n))) (setq ok nil reason "bad_idx"))
    ;; Left edge
    (if ok
      (progn
        (if (= iStart 0)
          (setq distLstar 0.0)
          (if (and (nth (1- iStart) needFlags) (nth iStart needFlags))
            (setq ok nil reason "L_TT")
            (if (and (not (nth (1- iStart) needFlags)) (nth iStart needFlags))
              (progn
                (setq x0 (car (nth (1- iStart) pts)) y0 (cadr (nth (1- iStart) pts)))
                (setq x1 (car (nth iStart pts)) y1 (cadr (nth iStart pts)))
                (cond
                  ;; En un nodo compartido puede cambiar la demanda sin delta de distancia.
                  ;; En ese caso el borde real del baston queda en el propio nodo.
                  ((equal x0 x1 1e-9)
                    (if (and (<= y0 asLong) (> y1 asLong))
                      (setq distLstar x1)
                      (setq ok nil reason "flat_L"))
                  )
                  ((equal y0 y1 1e-9)
                    (setq ok nil reason "flatY_L")
                  )
                  (T
                    (setq m (/ (- y1 y0) (- x1 x0)))
                    (setq b (- y0 (* m x0)))
                    (setq xStar (/ (- asLong b) m))
                    (setq inSeg (and (>= xStar (min x0 x1)) (<= xStar (max x0 x1))))
                    (princ (strcat "\nOCMEMA DBG: interp face=" face " edge=L pairIdx=(" (itoa (1- iStart)) "," (itoa iStart) ") dist=(" (rtos x0 2 3) "," (rtos x1 2 3) ") As=(" (rtos y0 2 3) "," (rtos y1 2 3) ") As_long=" (rtos asLong 2 3) " x*=" (rtos xStar 2 3) " ok=" (if inSeg "T" "N")))
                    (if inSeg (setq distLstar xStar) (setq ok nil reason "outseg_L"))
                  )
                )
              )
              (setq ok nil reason "L_noPair")
            )
          )
        )
      )
    )
    ;; Right edge
    (if ok
      (progn
        (if (= iEnd (1- n))
          (setq distRstar (if (numberp L_total_cm) L_total_cm (car (nth iEnd pts))))
          (if (and (nth iEnd needFlags) (not (nth (1+ iEnd) needFlags)))
            (progn
              (setq x0 (car (nth iEnd pts)) y0 (cadr (nth iEnd pts)))
              (setq x1 (car (nth (1+ iEnd) pts)) y1 (cadr (nth (1+ iEnd) pts)))
              (cond
                ;; Si el ultimo punto del miembro aun pide acero y el primero del siguiente ya no,
                ;; no se puede interpolar en X; se toma el nodo y se agrega 30 cm ademas de 12phi.
                ((equal x0 x1 1e-9)
                  (if (and (> y0 asLong) (<= y1 asLong))
                    (progn
                      (setq distRstar x0)
                      (setq addR_cm 30.0)
                    )
                    (setq ok nil reason "flat_R"))
                )
                ((equal y0 y1 1e-9)
                  (setq ok nil reason "flatY_R")
                )
                (T
                  (setq m (/ (- y1 y0) (- x1 x0)))
                  (setq b (- y0 (* m x0)))
                  (setq xStar (/ (- asLong b) m))
                  (setq inSeg (and (>= xStar (min x0 x1)) (<= xStar (max x0 x1))))
                  (princ (strcat "\nOCMEMA DBG: interp face=" face " edge=R pairIdx=(" (itoa iEnd) "," (itoa (1+ iEnd)) ") dist=(" (rtos x0 2 3) "," (rtos x1 2 3) ") As=(" (rtos y0 2 3) "," (rtos y1 2 3) ") As_long=" (rtos asLong 2 3) " x*=" (rtos xStar 2 3) " ok=" (if inSeg "T" "N")))
                  (if inSeg (setq distRstar xStar) (setq ok nil reason "outseg_R"))
                )
              )
            )
            (setq ok nil reason "R_noPair")
          )
        )
      )
    )
    (if ok
      (progn
        (setq Ld_cm (* 12.0 d_cm))
        (setq distL (- distLstar Ld_cm))
        (setq distR (+ distRstar Ld_cm addR_cm))
      )
    )
    (if (not ok)
      (progn
        (setq distLstar (car (nth iStart pts)))
        (setq distRstar (car (nth iEnd pts)))
        (setq Ld_cm 0.0)
        (setq distL distLstar distR distRstar)
        (princ (strcat "\nOCMEMA WARN: face=" face " zone fallback (no interpolate or no d)"))
      )
    )
    (list distLstar distRstar distL distR ok Ld_cm)
  )

  (defun ocmema--build-zones (pts limitMin tolX face / zones inZone startIdx endIdx lastReqX i n currX currReq)
    (setq zones '())
    (setq n (length pts))
    (if (>= n 2)
      (progn
        (setq i 0 inZone nil startIdx nil endIdx nil lastReqX nil)
        (while (< i n)
          (setq currX (car (nth i pts)) currReq (cadr (nth i pts)))
          (if (> currReq limitMin)
            (progn
              (if (not inZone)
                (progn (setq inZone T) (setq startIdx i) (setq endIdx i) (setq lastReqX currX))
                (progn
                  (if (and (numberp lastReqX) (> (- currX lastReqX) tolX))
                    (progn
                      (if (>= (- endIdx startIdx) 1)
                        (setq zones (append zones (list (list startIdx endIdx (car (nth startIdx pts)) (car (nth endIdx pts))))))
                      )
                      (setq startIdx i) (setq endIdx i)
                    )
                    (setq endIdx i)
                  )
                  (setq lastReqX currX)
                )
              )
            )
            (if inZone
              (progn
                (if (>= (- endIdx startIdx) 1)
                  (setq zones (append zones (list (list startIdx endIdx (car (nth startIdx pts)) (car (nth endIdx pts))))))
                )
                (setq inZone nil startIdx nil endIdx nil lastReqX nil)
              )
            )
          )
          (setq i (1+ i))
        )
        (if (and inZone (>= (- endIdx startIdx) 1))
          (setq zones (append zones (list (list startIdx endIdx (car (nth startIdx pts)) (car (nth endIdx pts))))))
        )
      )
    )
    (if (numberp n) (princ (strcat "\nOCMEMA DBG: face=" face " zones_found=" (itoa (length zones)) " stations=" (itoa n))))
    (setq i 0)
    (foreach z zones
      (princ (strcat "\nOCMEMA DBG: face=" face " zone#" (itoa (1+ i))
                     " idx=(" (itoa (nth 0 z)) ".." (itoa (nth 1 z)) ")"
                     " xApprox=(" (rtos (nth 2 z) 2 4) ".." (rtos (nth 3 z) 2 4) ")"))
      (setq i (1+ i))
    )
    zones
  )

  (defun ocmema--print-zone-deficits (pts iStart iEnd asLong face zoneIdx / i st dist_cm asReq deficit maxDef)
    (setq i iStart maxDef 0.0)
    (princ (strcat "\nResumen baston " face " #" (itoa zoneIdx) ":"))
    (while (<= i iEnd)
      (setq st (nth i pts))
      (setq dist_cm (car st))
      (setq asReq (cadr st))
      (if (not (numberp asReq)) (setq asReq 0.0))
      (setq deficit (- asReq asLong))
      (if (> deficit maxDef) (setq maxDef deficit))
      (princ
        (strcat
          "\n  dist=" (rtos dist_cm 2 3) " cm"
          " | As_req=" (rtos asReq 2 3)
          " | As_long=" (rtos asLong 2 3)
          " | Dif=" (rtos deficit 2 3)
        )
      )
      (setq i (1+ i))
    )
    (princ (strcat "\n  Dif maxima=" (rtos maxDef 2 3) " cm2"))
    maxDef
  )

  (defun ocmema--interp-borders (pts iStart iEnd limitMin d_cm face / n iL iR insideL outsideL insideR outsideR f_in_L f_out_L f_in_R f_out_R xLstar xRstar Ld_m xL xR ok reason)
    (setq n (length pts) ok T reason nil)
    (if (or (not (numberp d_cm)) (<= d_cm 0.0)) (setq ok nil reason "no_d"))
    (setq iL (1- iStart) iR (1+ iEnd))
    (if (and ok (or (< iStart 0) (< iEnd 0) (>= iStart n) (>= iEnd n) (< iL 0) (>= iR n)))
      (setq ok nil reason "no_bracket")
    )
    (if ok
      (progn
        (setq insideL (nth iStart pts) outsideL (nth iL pts))
        (setq insideR (nth iEnd pts) outsideR (nth iR pts))
        (setq f_in_L (- limitMin (cadr insideL))) (setq f_out_L (- limitMin (cadr outsideL)))
        (setq f_in_R (- limitMin (cadr insideR))) (setq f_out_R (- limitMin (cadr outsideR)))
        (if (or (< f_out_L 0.0) (< f_out_R 0.0)) (setq ok nil reason "no_bracket"))
      )
    )
    (if ok
      (progn
        (setq xLstar (obtener-x-interpolada (car outsideL) f_out_L (car insideL) f_in_L 0.0))
        (setq xRstar (obtener-x-interpolada (car insideR) f_in_R (car outsideR) f_out_R 0.0))
        (setq Ld_m (/ (* 12.0 d_cm) 100.0))
        (setq xL (- xLstar Ld_m))
        (setq xR (+ xRstar Ld_m))
        (if (or (> xL xLstar) (> xLstar xRstar) (> xRstar xR))
          (progn (setq ok nil reason "order"))
        )
      )
    )
    (if (not ok)
      (progn
        (setq xLstar (car (nth iStart pts)))
        (setq xRstar (car (nth iEnd pts)))
        (setq Ld_m 0.0)
        (setq xL xLstar xR xRstar)
        (princ (strcat "\nOCMEMA WARN: face=" face " zone fallback (no interpolate or no d)"))
      )
    )
    (princ (strcat "\nOCMEMA DBG: face=" face " zone idx=(" (itoa iStart) ".." (itoa iEnd) ")"
                   " x*=(" (rtos xLstar 2 4) "," (rtos xRstar 2 4) ")"
                   " d=" (rtos d_cm 2 3) " x=(" (rtos xL 2 4) "," (rtos xR 2 4) ")"))
    (list xLstar xRstar xL xR ok Ld_m)
  )

  ;; --- MOTOR DE ANALISIS (V27) ---
  (defun procesar-zonas-v27 (steelList limitMin x_origin_draw is_top / idx_val base ptsCorr zonas inZone startXZone endXZone maxReqZone i prev_x prev_req curr_x curr_req first_req last_x)
    (setq idx_val (if is_top 1 2)) (setq base (+ x_origin_draw 0.5))
    (setq ptsCorr '())
    (foreach pt steelList (if (and (numberp (car pt)) (numberp (nth idx_val pt))) (setq ptsCorr (append ptsCorr (list (list (+ base (car pt)) (nth idx_val pt)))))))
    (setq ptsCorr (vl-sort ptsCorr '(lambda (a b) (< (car a) (car b)))))
    (setq zonas '())
    (if (< (length ptsCorr) 2) zonas
      (progn
        (setq inZone nil startXZone nil endXZone nil maxReqZone 0.0)
        (setq first_req (cadr (car ptsCorr)))
        (if (> first_req limitMin) (progn (setq inZone T) (setq startXZone (car (car ptsCorr))) (setq maxReqZone first_req)))
        (setq i 1)
        (while (< i (length ptsCorr))
          (setq prev_x (car (nth (1- i) ptsCorr))) (setq prev_req (cadr (nth (1- i) ptsCorr)))
          (setq curr_x (car (nth i ptsCorr))) (setq curr_req (cadr (nth i ptsCorr)))
          (if (and (not inZone) (<= prev_req limitMin) (> curr_req limitMin)) (progn (setq inZone T) (setq startXZone (obtener-x-interpolada prev_x prev_req curr_x curr_req limitMin)) (setq maxReqZone (max prev_req curr_req))))
          (if inZone (setq maxReqZone (max maxReqZone curr_req)))
          (if (and inZone (> prev_req limitMin) (<= curr_req limitMin)) (progn (setq endXZone (obtener-x-interpolada prev_x prev_req curr_x curr_req limitMin)) (setq zonas (append zonas (list (list startXZone endXZone maxReqZone)))) (setq inZone nil startXZone nil endXZone nil maxReqZone 0.0)))
          (setq i (1+ i))
        )
        (if inZone (progn (setq last_x (car (last ptsCorr))) (setq zonas (append zonas (list (list startXZone last_x maxReqZone))))))
        zonas
      )
    )
  )

  (defun calc-puntos-v27 (x_interp_start x_interp_end axis_list / t_start t_end ax_s ax_e dist_s dist_e round_s round_e final_s final_e tmp)
    (setq t_start (- x_interp_start 0.20)) (setq t_end (+ x_interp_end 0.20))
    (setq ax_s (get-closest-axis t_start axis_list))
    (if ax_s (progn (setq dist_s (abs (- t_start ax_s))) (setq round_s (redondear-al-5 dist_s)) (setq final_s (if (< t_start ax_s) (- ax_s round_s) (+ ax_s round_s)))) (setq final_s t_start))
    (setq ax_e (get-closest-axis t_end axis_list))
    (if ax_e (progn (setq dist_e (abs (- t_end ax_e))) (setq round_e (redondear-al-5 dist_e)) (setq final_e (if (< t_end ax_e) (- ax_e round_e) (+ ax_e round_e)))) (setq final_e t_end))
    (if (> final_s final_e) (progn (setq tmp final_s) (setq final_s final_e) (setq final_e tmp)))
    (list final_s final_e)
  )

  (defun dibujar-leader-blindado (pt1 texto es_top es_final / sgn_y sgn_x pt2 pt3 obj_text obj_leader)
     (setvar "DIMCLRD" 7) (setvar "DIMASZ" 0.15) (setvar "DIMSCALE" 1.0)
     (setq sgn_y (if es_top -1.0 1.0)) (setq sgn_x (if es_final -1.0 1.0))
     (setq pt2 (list (+ (car pt1) (* 0.20 sgn_x)) (+ (cadr pt1) (* 0.35 sgn_y))))
     (setq pt3 (list (+ (car pt2) (* 0.15 sgn_x)) (cadr pt2)))
     (command "_.LEADER" pt1 pt2 pt3 "" "" "N")
     (if (setq obj_leader (vlax-ename->vla-object (entlast))) (vl-catch-all-apply 'vla-put-Color (list obj_leader 7)))
     (if (< (car pt3) (car pt2)) (command "_.TEXT" "_J" "_MR" pt3 0.15 0 texto) (command "_.TEXT" "_J" "_ML" pt3 0.15 0 texto))
     (setq obj_text (vlax-ename->vla-object (entlast))) (vl-catch-all-apply 'vla-put-Color (list obj_text 40)) 
  )

  (defun clean-string (s) (vl-string-translate "|" " " s))
  (defun *error* (msg) (if oldOsnap (setvar "OSMODE" oldOsnap)) (if (and fp (= (type fp) 'FILE)) (close fp)) (princ))

  (setq old_dimasz (getvar "DIMASZ")) (setq old_dimclrd (getvar "DIMCLRD")) (setq old_dimtxt (getvar "DIMTXT")) (setq old_dimclrt (getvar "DIMCLRT")) (setq old_dimscale (getvar "DIMSCALE"))
  (setq oldOsnap (getvar "OSMODE")) (setvar "OSMODE" 0) (setvar "CMDECHO" 0) (setvar "FILLETRAD" 0.05)
  (if (not (tblsearch "LTYPE" "CENTER")) (command "-LINETYPE" "Load" "CENTER" "acad.lin" ""))

  ;; ==============================================================================
  ;; 2. LECTURA DE DATOS
  ;; ==============================================================================
  (setq file anlPath)
  (if (or (not file) (= file ""))
    (setq file (getfiled "Seleccionar archivo TRABE (ANL)"
                          (if (vl-file-directory-p ocmema--default-project-dir) ocmema--default-project-dir "")
                          "ANL;TXT;OUT" 4))
  )
  (if (not file) (exit))
  (setq filename (vl-filename-base file)) (princ "\n1. Leyendo Geometria y Materiales...")
  (setq fp (open file "r"))
  (setq coordList nil YD 25.0 ZB 10.0 dataMode nil fc_val 200.0 supportNodes '())

  (while (setq line (read-line fp))
    (setq line (vl-string-trim " \t" line))
    (cond
      ((wcmatch line "* FC *") (setq cleanLine (clean-string line)) (setq tokenList (read (strcat "(" cleanLine ")"))) (setq k 0)
         (while (< k (length tokenList)) (if (and (eq (nth k tokenList) 'FC) (numberp (nth (1+ k) tokenList))) (setq fc_val (nth (1+ k) tokenList))) (setq k (1+ k))))
      ((or (wcmatch line "*JOINT COORDINATES*") (wcmatch line "*COORDENADAS*")) (setq dataMode "NODES"))
      ((and (= dataMode "NODES") (or (wcmatch line "*MEMBER INCIDENCES*") (wcmatch line "*INCIDENCIAS*"))) (setq dataMode nil))
      ((and (= dataMode "NODES") (> (strlen line) 0)) (if (numberp (read (substr line 1 1))) (progn (setq strList (read (strcat "(" (vl-string-translate "." " " line) ")"))) (setq valX nil nodeID nil) (cond ((>= (length strList) 5) (setq nodeID (nth 1 strList)) (setq valX (nth 2 strList))) ((= (length strList) 4) (setq nodeID (nth 0 strList)) (setq valX (nth 1 strList)))) (if (numberp valX) (setq coordList (append coordList (list (list nodeID valX))))))))
      ((wcmatch line "*MEMBER PROPERTY*") (setq dataMode "PROPS"))
      ((wcmatch line "*SUPPORTS*") (setq dataMode "SUPPORTS"))
      ((or (wcmatch line "*UNIT *") (wcmatch line "*START CONCRETE DESIGN*")) (if (= dataMode "SUPPORTS") (setq dataMode nil)))
      ((and (= dataMode "PROPS") (wcmatch line "*PRIS*")) (if (setq pos (vl-string-search "YD" line)) (setq YD (atof (substr line (+ pos 4) 5)))) (if (setq pos (vl-string-search "ZB" line)) (setq ZB (atof (substr line (+ pos 4) 5))) (if (setq pos (vl-string-search "ZD" line)) (setq ZB (atof (substr line (+ pos 4) 5))))) (setq dataMode nil))
      ((and (= dataMode "SUPPORTS") (> (strlen line) 0)) (foreach nSupp (ocmema--support-ids-from-line line) (if (not (member nSupp supportNodes)) (setq supportNodes (append supportNodes (list nSupp))))))
    )
  )
  (close fp)

  (if (null coordList) (progn (alert "No se pudo leer la geometria.") (exit)))
  (setq coordList (vl-sort coordList '(lambda (a b) (< (cadr a) (cadr b)))))
  (setq startX (cadr (nth 0 coordList))) (setq endX (cadr (last coordList)))
  (setq l_total_cm (- endX startX)) (setq l_total_m (/ l_total_cm 100.0)) (setq h_cm YD b_cm ZB)
  (setq h_draw (* (/ h_cm 100.0) 7.0)) (setq rectLen (+ l_total_m 1.0))

  (setq memberOffsetList '())
  (foreach node coordList (setq memberOffsetList (append memberOffsetList (list (/ (- (cadr node) startX) 100.0)))))
  (if (> (length memberOffsetList) 0) (setq memberOffsetList (reverse (cdr (reverse memberOffsetList)))))

  (princ "\n2. Procesando Acero...")
  (setq dir (vl-filename-directory file)) (setq tempFile (strcat dir "\\" filename "_TEMP_ANSI.TXT"))
  (setq wsh (vlax-create-object "WScript.Shell"))
  (setq cmd (strcat "powershell -NoProfile -Command \"Get-Content -LiteralPath '" file "' | Set-Content -Encoding Ascii '" tempFile "'\""))
  (vlax-invoke wsh 'Run cmd 0 :vlax-true) (vlax-release-object wsh)

  (setq fp (open tempFile "r"))
  (setq globalSteelList '() xOffsetGlobal 0.0) (setq isReadingSteel nil savedDist nil) (setq astTop 0.0 astBot 0.0) (setq mIndex 0)

  (while (setq line (read-line fp))
    (setq cleanLine (clean-string line)) 
    (if (wcmatch line "*LONGITUDINAL BAR DETAILS*") (setq isReadingSteel T savedDist nil))
    (if (and isReadingSteel (wcmatch line "*LONGITUDINAL BAR LAYOUT*"))
      (progn
        (if savedDist (setq globalSteelList (append globalSteelList (list (list (+ xOffsetGlobal savedDist) astTop astBot)))))
        (setq savedDist nil)
        (setq isReadingSteel nil)
      )
    )
    (if (wcmatch line "*Member *:*") (progn (setq mIndex (1+ mIndex)) (setq savedDist nil) (if (and memberOffsetList (<= mIndex (length memberOffsetList))) (setq xOffsetGlobal (nth (1- mIndex) memberOffsetList)) (if (> (length globalSteelList) 0) (setq xOffsetGlobal (car (last globalSteelList))) (setq xOffsetGlobal 0.0)))))
    (if (and isReadingSteel (> (strlen cleanLine) 5) (not (wcmatch line "*Distance*")) (not (wcmatch line "*-----*")))
      (progn (setq tokenList (read (strcat "(" cleanLine ")")))
        (cond ((numberp (car tokenList)) (if savedDist (setq globalSteelList (append globalSteelList (list (list (+ xOffsetGlobal savedDist) astTop astBot))))) (setq savedDist (/ (nth 0 tokenList) 100.0)) (setq valAst (nth 2 tokenList)) (if (eq (nth 1 tokenList) 'Top) (setq astTop valAst) (setq astBot valAst)) (if (eq (nth 1 tokenList) 'Top) (setq astBot 0.0) (setq astTop 0.0)))
              ((or (eq (car tokenList) 'Top) (eq (car tokenList) 'Bottom)) (if savedDist (progn (setq valAst (nth 1 tokenList)) (if (eq (car tokenList) 'Top) (setq astTop valAst)) (if (eq (car tokenList) 'Bottom) (setq astBot valAst))))))))
  )
  (if savedDist (setq globalSteelList (append globalSteelList (list (list (+ xOffsetGlobal savedDist) astTop astBot)))))
  (close fp) (vl-file-delete tempFile)
  (setq globalSteelList (mapcar '(lambda (pt) (list (car pt) (cadr pt) (caddr pt))) globalSteelList))
  (setq maxDemBot 0.0 maxDemTop 0.0)
  (foreach pt globalSteelList
    (if (and (numberp (cadr pt)) (numberp (caddr pt)))
      (progn (setq maxDemBot (max maxDemBot (caddr pt))) (setq maxDemTop (max maxDemTop (cadr pt))))
      (princ (strcat "\nOCMEMA WARN: steel point with nil values skipped: " (vl-princ-to-string pt)))
    )
  )

  ;; 3. DIBUJO BASE
  (princ "\nSeleccione punto de origen: ") (setq ptOrigin (getpoint)) (if (not ptOrigin) (exit)) (setq xOrigin (car ptOrigin) yOrigin (cadr ptOrigin))
  
  (command "_.TEXT" "_J" "_TL" (list xOrigin (+ yOrigin 0.33)) 0.25 0 (strcat "h=" (rtos h_cm 2 0))) (command "_.CHPROP" (entlast) "" "Color" 3 "")
  (command "_.TEXT" "_J" "_TL" (list xOrigin (+ yOrigin 0.86)) 0.25 0 (strcat "b=" (rtos b_cm 2 0))) (command "_.CHPROP" (entlast) "" "Color" 3 "")
  (command "_.TEXT" "_J" "_TL" (list xOrigin (+ yOrigin h_draw)) 0.35 0 filename) (command "_.CHPROP" (entlast) "" "Color" 4 "")
  
  (setq widthName (* (strlen filename) 0.28))
  (setq p1 (list (+ xOrigin widthName 0.3) yOrigin)) 
  (setq p2 (list (+ (car p1) rectLen) (+ yOrigin h_draw)))
  (command "_.RECTANG" p1 p2) (command "_.CHPROP" (entlast) "" "Color" 7 "")

  (setq numNodes (length coordList))
  (setq projectItem (ocmema--find-project-item-local "beams" filename))
  (setq projectPlant nil)
  (setq projectPoints nil)
  (setq axisPairsX nil)
  (setq axisPairsY nil)
  (setq axisTolDraw (ocmema--axis-tol-draw))
  (setq autoAxisFamily nil)
  (setq autoAxisEnabled nil)
  (setq hasProjectAxes nil)
  (setq useModel3dAxis nil)
  (setq projectPointNodeMap nil)
  (if projectItem
    (progn
      (setq useModel3dAxis (ocmema--meta-model3d-p (ocmema--alist-get-local "meta_kv" projectItem)))
      (setq projectPoints (ocmema--alist-get-local "points_raw" projectItem))
      (if (listp projectPoints)
        (setq autoAxisFamily (ocmema--axis-family-from-points projectPoints axisTolDraw))
      )
      (setq projectPlant (ocmema--find-plant-local (ocmema--alist-get-local "plant_idx" projectItem)))
      (if (and (not projectPlant) autoAxisFamily projectPoints)
        (setq projectPlant (ocmema--best-plant-local projectPoints autoAxisFamily axisTolDraw))
      )
      (setq axisPairsX (if projectPlant (ocmema--alist-get-local "x_axes" projectPlant) nil))
      (setq axisPairsY (if projectPlant (ocmema--alist-get-local "y_axes" projectPlant) nil))
      (setq hasProjectAxes (or (and (listp axisPairsX) (> (length axisPairsX) 0))
                               (and (listp axisPairsY) (> (length axisPairsY) 0))))
      (if (and autoAxisFamily projectPoints)
        (progn
          (setq projectPointNodeMap (ocmema--map-points-to-node-indexes projectPoints autoAxisFamily coordList startX))
          (if (= projectPointNodeMap 'ERR_MORE_POINTS)
            (progn
              (setq projectPointNodeMap nil)
              (prompt "\nOCMEMA WARN: Hay mas puntos guardados en TXT que nodos en el ANL. Se desactiva auto-eje.")
            )
          )
        )
      )
      (setq autoAxisEnabled (and useModel3dAxis hasProjectAxes autoAxisFamily projectPoints (listp projectPointNodeMap)))
    )
  )

  (setq axisXList '()) (setq idx 0 dimXList '())
  (foreach node coordList
    (setq nID (car node) nX_m (/ (- (cadr node) startX) 100.0))
    (setq axisName "")
    (setq posType "Centrado")
    (setq drawRed nil)
    (setq drawX 0.0 extraX nil)
    (setq isSupportNode (or (= idx 0) (= idx (1- numNodes)) (member nID supportNodes)))
    (setq mappedPoint (if autoAxisEnabled (ocmema--mapped-point-for-node-index idx projectPointNodeMap projectPoints) nil))
    (setq autoAxisName (if mappedPoint (ocmema--auto-axis-name-for-index (cdr (assoc idx projectPointNodeMap)) projectPoints autoAxisFamily axisPairsX axisPairsY axisTolDraw) nil))
    (cond
      (autoAxisName
        (setq hasAxis T)
        (setq drawRed T)
        (setq axisName autoAxisName)
      )
      ((and useModel3dAxis autoAxisEnabled mappedPoint)
        (setq hasAxis nil)
        (setq drawRed T)
      )
      ((and useModel3dAxis autoAxisEnabled)
        (setq hasAxis nil)
        (setq drawRed nil)
      )
      (useModel3dAxis
        (cond
          ((or (= idx 0) (= idx (1- numNodes)))
            (princ (strcat "\nNodo extremo " (itoa nID) "..."))
            (initget "Si No")
            (setq hasAxis (getkword " Eje? [Si/No] <Si>: "))
            (if (null hasAxis) (setq hasAxis "Si"))
            (setq hasAxis (= hasAxis "Si"))
            (setq drawRed T)
            (if hasAxis
              (progn
                (setq axisName (getstring T " Nombre del eje: "))
                (if (= axisName "") (setq axisName (itoa (1+ idx))))
              )
            )
          )
          (T
            (princ (strcat "\nNodo " (itoa nID) "..."))
            (initget "Si No")
            (setq hasAxis (getkword " Eje? [Si/No] <No>: "))
            (if (null hasAxis) (setq hasAxis "No"))
            (setq hasAxis (= hasAxis "Si"))
            (if hasAxis
              (progn
                (setq drawRed T)
                (setq axisName (getstring T " Nombre del eje: "))
                (if (= axisName "") (setq axisName (itoa (1+ idx))))
              )
              (progn
                (initget "Si No")
                (setq drawRed (getkword " Dibujar linea roja? [Si/No] <No>: "))
                (if (null drawRed) (setq drawRed "No"))
                (setq drawRed (= drawRed "Si"))
              )
            )
          )
        )
      )
      (isSupportNode
        (princ (strcat "\nNodo " (itoa nID) (if (or (= idx 0) (= idx (1- numNodes))) " (apoyo extremo)..." " (apoyo)...")))
        (initget "Si No")
        (setq hasAxis (getkword " Eje? [Si/No] <Si>: "))
        (if (null hasAxis) (setq hasAxis "Si"))
        (setq hasAxis (= hasAxis "Si"))
        (setq drawRed T)
        (if hasAxis
          (progn
            (setq axisName (getstring T " Nombre del eje: "))
            (if (= axisName "") (setq axisName (itoa (1+ idx))))
          )
        )
      )
      (T
        (setq hasAxis nil)
        (setq drawRed nil)
      )
    )
    (if (and drawRed (or (= idx 0) (= idx (1- numNodes))) (not autoAxisEnabled) (or isSupportNode useModel3dAxis autoAxisName))
      (progn
        (initget "Orillado Centrado")
        (setq posType (getkword " Pos? [Orillado/Centrado] <Centrado>: "))
        (if (null posType) (setq posType "Centrado"))
      )
    )
    (if (= idx 0)
      (if (= posType "Orillado") (progn (setq drawX (+ (car p1) 0.0)) (setq extraX (+ (car p1) 0.5))) (setq drawX (+ (car p1) 0.5)))
      (if (= idx (1- numNodes))
        (if (= posType "Orillado") (progn (setq drawX (+ (car p1) rectLen)) (setq extraX (+ (car p1) rectLen -0.5))) (setq drawX (+ (car p1) 0.5 nX_m)))
        (setq drawX (+ (car p1) 0.5 nX_m))
      )
    )
    (setq axisCenter (+ (car p1) 0.5 nX_m))
    (if drawRed
      (progn
        (setq axisXList (append axisXList (list axisCenter))) (setq dimXList (append dimXList (list axisCenter)))
        (setq pAxisBot (list drawX (- yOrigin 0.5)) pAxisTop (list drawX (+ yOrigin h_draw 1.25)))
        (command "_.LINE" pAxisBot pAxisTop "") (command "_.CHPROP" (entlast) "" "Color" 1 "Ltype" "CENTER" "Ltscale" 0.3 "")
        (if extraX (progn (command "_.LINE" (list extraX (- yOrigin 0.5)) (list extraX (+ yOrigin h_draw 1.25)) "") (command "_.CHPROP" (entlast) "" "Color" 1 "Ltype" "CENTER" "Ltscale" 0.3 "")))
        (if hasAxis (progn (setq centerCircle (list drawX (+ (cadr pAxisTop) 0.275))) (command "_.CIRCLE" centerCircle 0.275) (command "_.CHPROP" (entlast) "" "Color" 7 "") (command "_.TEXT" "_MC" centerCircle 0.22 0 axisName) (command "_.CHPROP" (entlast) "" "Color" 4 "")))
      )
    )
    (setq idx (1+ idx))
  )
  (setq yTopRed (+ yOrigin h_draw 1.25) yDimLoc (- yTopRed 0.25) i 0)
  (repeat (1- (length dimXList)) (command "_.DIMLINEAR" (list (nth i dimXList) yTopRed) (list (nth (1+ i) dimXList) yTopRed) (list (/ (+ (nth i dimXList) (nth (1+ i) dimXList)) 2.0) yDimLoc)) (setq i (1+ i)))

  (setq asMinFormula (* (/ (* 0.8 (sqrt fc_val)) 4200.0) b_cm (- h_cm 3.0)))
  (princ (strcat "\n\n*** F'c: " (rtos fc_val 2 0) " | As Min (ACI): " (rtos asMinFormula 2 3) " ***"))
  (princ "\nOCMEMA WARN: TEMP steel logic/drawing not found in DIBUJAR_TRABE_V_FINAL_FIXED10; skipped")

  (setq tolX 0.005)

  (princ "\nOCMEMA DBG: entrando a ACERO INFERIOR")
  ;; 4. ACERO INFERIOR
  (princ "\n--- ACERO INFERIOR ---") (setq yBot (+ yOrigin 0.15)) (setq x_ini_inf (+ (car p1) 0.15)) (setq x_fin_inf (- (car p2) 0.15))
  (princ (strcat "\nAs requerido base inferior: " (rtos asMinFormula 2 3) " cm2"))
  (setq strVarBaseBot (ocmema:ask-base-varilla "\nNumero varilla Base Inf (ej. 3, 4): "))
  (princ (strcat "\nOCMEMA DBG: baseInf final=" (vl-princ-to-string strVarBaseBot)))
  (setq areaBarBot (obtener-area-varilla strVarBaseBot))
  (if (> areaBarBot 0.0) (progn (setq qtyRecBot (fix (+ (/ asMinFormula areaBarBot) 0.9999))) (princ (strcat "\n-> Sugerido: " (itoa qtyRecBot) " varillas.")) (setq numBaseBot (getint (strcat "\nCantidad definitiva <" (itoa qtyRecBot) ">: "))) (if (null numBaseBot) (setq numBaseBot qtyRecBot))) (progn (setq numBaseBot 0) (princ "\nVarilla 0.")))
  (setq asBaseBot (* numBaseBot areaBarBot))
  (princ (strcat "\nOCMEMA DBG: BOT baseBar=" strVarBaseBot " qty=" (itoa numBaseBot) " As_long=" (rtos asBaseBot 2 3)))
  (command "_.PLINE" (list x_ini_inf (+ yBot 0.30)) (list x_ini_inf yBot) (list x_fin_inf yBot) (list x_fin_inf (+ yBot 0.30)) "") (command "_.CHPROP" (entlast) "" "Color" 5 "") (command "_.FILLET" "P" (entlast))
  (dibujar-leader-blindado (list (/ (+ x_ini_inf x_fin_inf) 2.0) yBot) (strcat (itoa numBaseBot) "#" strVarBaseBot) nil nil)

  (setq bastonesInfList '())
  (if (> maxDemBot asBaseBot)
    (progn
       (setq ptsCorrInf (ocmema--build-pts-dist globalSteelList 2))
       (setq x_support0 (+ (car p1) 0.5))
       (setq x_supportL (+ x_support0 l_total_m))
       (setq scaleX 0.01)
       (setq needFlags '() needIdxT '() zonesIdx '())
       (setq i 0)
       (foreach st ptsCorrInf
         (setq i (1+ i))
         (setq dist_cm (car st)) (setq streq (cadr st))
         (if (not (numberp streq))
           (progn (princ (strcat "\nOCMEMA WARN: As_req NIL at st#" (itoa i) " face=BOT")) (setq streq 0.0))
         )
         (setq needFlag (> streq (+ asBaseBot 0.000001)))
         (setq needFlags (append needFlags (list needFlag)))
         (if needFlag (setq needIdxT (append needIdxT (list i))))
         (setq x_draw_calc (ocmema:dist->x dist_cm x_support0 scaleX))
         (princ (strcat "\nOCMEMA DBG: BOT st#" (itoa i)
                        " dist_cm=" (rtos dist_cm 2 3)
                        " x0=" (rtos x_support0 2 4)
                        " x_draw_calc=" (rtos x_draw_calc 2 4)
                        " x_draw_used=" (rtos x_draw_calc 2 4)
                        " As_req=" (rtos streq 2 3)
                        " As_long=" (rtos asBaseBot 2 3)
                        " need?=" (if needFlag "T" "N")))
       )
       (princ (strcat "\nOCMEMA DBG: units check As_req sample=" (if (and ptsCorrInf (numberp (cadr (car ptsCorrInf)))) (rtos (cadr (car ptsCorrInf)) 2 3) "nil")
                      " As_long=" (rtos asBaseBot 2 3)))
       (setq distDeltaStr "")
       (setq i 1)
       (while (< i (length ptsCorrInf))
         (setq distDeltaStr (strcat distDeltaStr (rtos (- (car (nth i ptsCorrInf)) (car (nth (1- i) ptsCorrInf))) 2 3) " "))
         (setq i (1+ i))
       )
       (princ (strcat "\nOCMEMA DBG: BOT dist_cm deltas = " distDeltaStr))
       (princ (strcat "\nOCMEMA DBG: face=BOT needIdxT=" (vl-princ-to-string needIdxT)))
       (setq zonesInf '())
       (setq i 0)
       (setq n (length needFlags))
       (while (< i n)
         (if (nth i needFlags)
           (progn
             (setq iStart i)
             (while (and (< i n) (nth i needFlags)) (setq i (1+ i)))
             (setq iEnd (1- i))
             (setq zonesInf (append zonesInf (list (list iStart iEnd (car (nth iStart ptsCorrInf)) (car (nth iEnd ptsCorrInf))))))
             (setq zonesIdx (append zonesIdx (list (list (1+ iStart) (1+ iEnd)))))
           )
           (setq i (1+ i))
         )
       )
       (princ (strcat "\nOCMEMA DBG: face=BOT zones_found=" (itoa (length zonesInf)) " zones=" (vl-princ-to-string zonesIdx)))
       (princ (strcat "\nOCMEMA DBG: x_support0=" (rtos x_support0 2 4) " x_supportL=" (rtos x_supportL 2 4) " scaleX=" (rtos scaleX 2 3)))
       (setq zoneIdx 0)
       (foreach z zonesInf
          (setq zoneIdx (1+ zoneIdx))
          (setq iStart (nth 0 z)) (setq iEnd (nth 1 z))
          (setq distLstar (nth 2 z)) (setq distRstar (nth 3 z))
          (princ (strcat "\nOCMEMA DBG: BOT baston#" (itoa zoneIdx) " zone=(" (rtos distLstar 2 3) ".." (rtos distRstar 2 3) ") -> pedir calibre"))
          (setq deficit (ocmema--print-zone-deficits ptsCorrInf iStart iEnd asBaseBot "INF" zoneIdx))
          (setq strVarBast (ocmema:ask-baston-calibre))
          (if (or (null strVarBast) (not (ocmema--valid-bar? strVarBast)))
            (progn (princ "\nOCMEMA WARN: calibre baston invalido, usando default 3") (setq strVarBast "3"))
          )
          (setq d_baston_cm (obtener-diametro-real strVarBast))
          (princ (strcat "\nOCMEMA DBG: BOT baston#" (itoa zoneIdx) " calibre=" strVarBast " d_cm=" (rtos d_baston_cm 2 3)))
          (setq borders (ocmema--interp-borders-dist ptsCorrInf needFlags iStart iEnd asBaseBot d_baston_cm "BOT" l_total_cm))
          (setq distLstar (nth 0 borders)) (setq distRstar (nth 1 borders))
          (setq distL (nth 2 borders)) (setq distR (nth 3 borders)) (setq ok (nth 4 borders)) (setq Ld_cm (nth 5 borders))
          (if (numberp distL) (setq distL (ocmema--floor5cm distL)))
          (if (numberp distR) (setq distR (ocmema--ceil5cm distR)))
          (if (and (numberp distL) (< distL 0.0)) (progn (princ "\nOCMEMA WARN: distL<0, clamp a 0") (setq distL 0.0)))
          (if (and (numberp distR) (> distR l_total_cm)) (progn (princ "\nOCMEMA WARN: distR>L, clamp a L") (setq distR l_total_cm)))
          (if (and (numberp distL) (<= distL 20.0)) (setq distL 0.0))
          (if (and (numberp distR) (<= (- l_total_cm distR) 20.0)) (setq distR l_total_cm))
          (setq xLstar (ocmema:dist->x distLstar x_support0 scaleX))
          (setq xRstar (ocmema:dist->x distRstar x_support0 scaleX))
          (setq x_real_L (ocmema:dist->x distL x_support0 scaleX))
          (setq x_real_R (ocmema:dist->x distR x_support0 scaleX))
          (setq xL x_real_L)
          (setq xR x_real_R)
          (princ (strcat "\nOCMEMA DBG: face=BOT zone#" (itoa zoneIdx) " dist*=(" (rtos distLstar 2 3) "," (rtos distRstar 2 3) ") Ld_cm=" (rtos Ld_cm 2 3) " dist=(" (rtos distL 2 3) "," (rtos distR 2 3) ")"))
          (princ (strcat "\nOCMEMA DBG: face=BOT zone#" (itoa zoneIdx) " x*=(" (rtos xLstar 2 4) "," (rtos xRstar 2 4) ") x=(" (rtos xL 2 4) "," (rtos xR 2 4) ")"))
          (setq x_baston_ini x_real_L) (setq x_baston_fin x_real_R)
          (setq visExtraL 0.0) (setq visExtraR 0.0)
          (if (and (numberp distL) (= distL 0.0)) (setq visExtraL 0.25))
          (if (and (numberp distR) (= distR l_total_cm)) (setq visExtraR 0.25))
          (setq x_draw_L (- x_baston_ini visExtraL))
          (setq x_draw_R (+ x_baston_fin visExtraR))
          (setq deltaL (- x_real_L x_draw_L)) (setq deltaR (- x_draw_R x_real_R))
          (princ (strcat "\nOCMEMA DBG: baston face=BOT dist_real_cm=(" (rtos distL 2 3) "," (rtos distR 2 3) ") L_real_cm=" (rtos l_total_cm 2 3)))
          (princ (strcat "\nOCMEMA DBG: x_real=(" (rtos x_real_L 2 4) "," (rtos x_real_R 2 4) ") x_draw=(" (rtos x_draw_L 2 4) "," (rtos x_draw_R 2 4) ") extra=(" (rtos visExtraL 2 2) "," (rtos visExtraR 2 2) ")"))
          (princ (strcat "\nOCMEMA DBG: len_from_dist=" (rtos (/ (- distR distL) 100.0) 2 2) "m"))
          (princ (strcat "\nOCMEMA DBG: extra_check face=BOT dist=(" (rtos distL 2 3) ".." (rtos distR 2 3) ") L_real_cm=" (rtos l_total_cm 2 3) " deltaL=" (rtos deltaL 2 3) " deltaR=" (rtos deltaR 2 3)))
          (if (= distL 0.0)
            (princ (strcat "\nOCMEMA DBG: assert extraL=" (rtos (abs (- (- x_real_L x_draw_L) 0.25)) 2 3)))
            (princ (strcat "\nOCMEMA DBG: assert extraL=" (rtos (abs (- x_real_L x_draw_L)) 2 3)))
          )
          (if (= distR l_total_cm)
            (princ (strcat "\nOCMEMA DBG: assert extraR=" (rtos (abs (- (- x_draw_R x_real_R) 0.25)) 2 3)))
            (princ (strcat "\nOCMEMA DBG: assert extraR=" (rtos (abs (- x_draw_R x_real_R)) 2 3)))
          )
          (setq x_baston_ini x_draw_L) (setq x_baston_fin x_draw_R)
          (setq clampL (- x_support0 visExtraL))
          (setq clampR (+ x_supportL visExtraR))
          (if (< x_baston_ini clampL) (setq x_baston_ini clampL))
          (if (> x_baston_fin clampR) (setq x_baston_fin clampR))
                (command "_.PLINE" (list x_baston_ini (+ yBot 0.45)) (list x_baston_ini (+ yBot 0.15)) (list x_baston_fin (+ yBot 0.15)) (list x_baston_fin (+ yBot 0.45)) "") (command "_.CHPROP" (entlast) "" "Color" 5 "") (command "_.FILLET" "P" (entlast))
                (if (> distL 0.0)
                  (progn
                    (setq axis_near_start (get-closest-axis x_real_L axisXList))
                    (if axis_near_start (command "_.DIMLINEAR" (list axis_near_start yOrigin) (list x_real_L yOrigin) (list (/ (+ axis_near_start x_real_L) 2.0) (- yOrigin 0.4))))
                  )
                )
                (if (< distR l_total_cm)
                  (progn
                    (setq axis_near_end (get-closest-axis x_real_R axisXList))
                    (if axis_near_end (command "_.DIMLINEAR" (list x_real_R yOrigin) (list axis_near_end yOrigin) (list (/ (+ x_real_R axis_near_end) 2.0) (- yOrigin 0.4))))
                  )
                )
                (princ (strcat "\nBaston Inf Req: " (rtos deficit 2 2) " cm2. Long: " (rtos (/ (- distR distL) 100.0) 2 2) "m"))
                (setq areaBastOne (obtener-area-varilla strVarBast))
                (if (> areaBastOne 0.0) (progn (setq qtyBastRec (fix (+ (/ deficit areaBastOne) 0.9999))) (princ (strcat " Sugerido: " (itoa qtyBastRec))) (setq numBast (getint "\nCantidad definitiva: ")) (if (null numBast) (setq numBast qtyBastRec))) (setq numBast 1))
                (dibujar-leader-blindado (list (/ (+ x_baston_ini x_baston_fin) 2.0) (+ yBot 0.15)) (strcat (itoa numBast) "#" strVarBast) nil nil)
                (setq bastonesInfList (append bastonesInfList (list (list strVarBast numBast))))
       )
    )
    (princ (strcat "\n>>> Acero base cubre demanda Inf."))
  )

  (princ "\nOCMEMA DBG: entrando a ACERO SUPERIOR")
  ;; 5. ACERO SUPERIOR
  (princ "\n--- ACERO SUPERIOR ---") (setq yTop (+ yOrigin h_draw -0.15))
  (princ (strcat "\nAs requerido base superior: " (rtos asMinFormula 2 3) " cm2"))
  (setq strVarBaseTop (ocmema:ask-base-varilla "\nNumero varilla Base Sup (ej. 3, 4): "))
  (princ (strcat "\nOCMEMA DBG: baseSup final=" (vl-princ-to-string strVarBaseTop)))
  (setq areaBarTop (obtener-area-varilla strVarBaseTop))
  (if (> areaBarTop 0.0) (progn (setq qtyRecTop (fix (+ (/ asMinFormula areaBarTop) 0.9999))) (princ (strcat "\n-> Sugerido: " (itoa qtyRecTop) " varillas.")) (setq numBaseTop (getint (strcat "\nCantidad definitiva <" (itoa qtyRecTop) ">: "))) (if (null numBaseTop) (setq numBaseTop qtyRecTop))) (progn (setq numBaseTop 0) (princ "\nVarilla 0.")))
  (setq asBaseTop (* numBaseTop areaBarTop))
  (princ (strcat "\nOCMEMA DBG: TOP baseBar=" strVarBaseTop " qty=" (itoa numBaseTop) " As_long=" (rtos asBaseTop 2 3)))
  (command "_.PLINE" (list x_ini_inf (- yTop 0.30)) (list x_ini_inf yTop) (list x_fin_inf yTop) (list x_fin_inf (- yTop 0.30)) "") (command "_.CHPROP" (entlast) "" "Color" 5 "") (command "_.FILLET" "P" (entlast))
  (dibujar-leader-blindado (list (/ (+ x_ini_inf x_fin_inf) 2.0) yTop) (strcat (itoa numBaseTop) "#" strVarBaseTop) T nil)

  (setq bastonesSupList '())
  (if (> maxDemTop asBaseTop)
    (progn
       (setq ptsCorrSup (ocmema--build-pts-dist globalSteelList 1))
       (setq x_support0 (+ (car p1) 0.5))
       (setq x_supportL (+ x_support0 l_total_m))
       (setq scaleX 0.01)
       (setq needFlags '() needIdxT '() zonesIdx '())
       (setq i 0)
       (foreach st ptsCorrSup
         (setq i (1+ i))
         (setq dist_cm (car st)) (setq streq (cadr st))
         (if (not (numberp streq))
           (progn (princ (strcat "\nOCMEMA WARN: As_req NIL at st#" (itoa i) " face=TOP")) (setq streq 0.0))
         )
         (setq needFlag (> streq (+ asBaseTop 0.000001)))
         (setq needFlags (append needFlags (list needFlag)))
         (if needFlag (setq needIdxT (append needIdxT (list i))))
         (setq x_draw_calc (ocmema:dist->x dist_cm x_support0 scaleX))
         (princ (strcat "\nOCMEMA DBG: TOP st#" (itoa i)
                        " dist_cm=" (rtos dist_cm 2 3)
                        " x0=" (rtos x_support0 2 4)
                        " x_draw_calc=" (rtos x_draw_calc 2 4)
                        " x_draw_used=" (rtos x_draw_calc 2 4)
                        " As_req=" (rtos streq 2 3)
                        " As_long=" (rtos asBaseTop 2 3)
                        " need?=" (if needFlag "T" "N")))
       )
       (princ (strcat "\nOCMEMA DBG: units check As_req sample=" (if (and ptsCorrSup (numberp (cadr (car ptsCorrSup)))) (rtos (cadr (car ptsCorrSup)) 2 3) "nil")
                      " As_long=" (rtos asBaseTop 2 3)))
       (setq distDeltaStr "")
       (setq i 1)
       (while (< i (length ptsCorrSup))
         (setq distDeltaStr (strcat distDeltaStr (rtos (- (car (nth i ptsCorrSup)) (car (nth (1- i) ptsCorrSup))) 2 3) " "))
         (setq i (1+ i))
       )
       (princ (strcat "\nOCMEMA DBG: TOP dist_cm deltas = " distDeltaStr))
       (princ (strcat "\nOCMEMA DBG: face=TOP needIdxT=" (vl-princ-to-string needIdxT)))
       (setq zonesSup '())
       (setq i 0)
       (setq n (length needFlags))
       (while (< i n)
         (if (nth i needFlags)
           (progn
             (setq iStart i)
             (while (and (< i n) (nth i needFlags)) (setq i (1+ i)))
             (setq iEnd (1- i))
             (setq zonesSup (append zonesSup (list (list iStart iEnd (car (nth iStart ptsCorrSup)) (car (nth iEnd ptsCorrSup))))))
             (setq zonesIdx (append zonesIdx (list (list (1+ iStart) (1+ iEnd)))))
           )
           (setq i (1+ i))
         )
       )
       (princ (strcat "\nOCMEMA DBG: face=TOP zones_found=" (itoa (length zonesSup)) " zones=" (vl-princ-to-string zonesIdx)))
       (princ (strcat "\nOCMEMA DBG: x_support0=" (rtos x_support0 2 4) " x_supportL=" (rtos x_supportL 2 4) " scaleX=" (rtos scaleX 2 3)))
       (setq zoneIdx 0)
       (foreach z zonesSup
          (setq zoneIdx (1+ zoneIdx))
          (setq iStart (nth 0 z)) (setq iEnd (nth 1 z))
          (setq distLstar (nth 2 z)) (setq distRstar (nth 3 z))
          (princ (strcat "\nOCMEMA DBG: TOP baston#" (itoa zoneIdx) " zone=(" (rtos distLstar 2 3) ".." (rtos distRstar 2 3) ") -> pedir calibre"))
          (setq deficit (ocmema--print-zone-deficits ptsCorrSup iStart iEnd asBaseTop "SUP" zoneIdx))
          (setq strVarBast (ocmema:ask-baston-calibre))
          (if (or (null strVarBast) (not (ocmema--valid-bar? strVarBast)))
            (progn (princ "\nOCMEMA WARN: calibre baston invalido, usando default 3") (setq strVarBast "3"))
          )
          (setq d_baston_cm (obtener-diametro-real strVarBast))
          (princ (strcat "\nOCMEMA DBG: TOP baston#" (itoa zoneIdx) " calibre=" strVarBast " d_cm=" (rtos d_baston_cm 2 3)))
          (setq borders (ocmema--interp-borders-dist ptsCorrSup needFlags iStart iEnd asBaseTop d_baston_cm "TOP" l_total_cm))
          (setq distLstar (nth 0 borders)) (setq distRstar (nth 1 borders))
          (setq distL (nth 2 borders)) (setq distR (nth 3 borders)) (setq ok (nth 4 borders)) (setq Ld_cm (nth 5 borders))
          (if (numberp distL) (setq distL (ocmema--floor5cm distL)))
          (if (numberp distR) (setq distR (ocmema--ceil5cm distR)))
          (if (and (numberp distL) (< distL 0.0)) (progn (princ "\nOCMEMA WARN: distL<0, clamp a 0") (setq distL 0.0)))
          (if (and (numberp distR) (> distR l_total_cm)) (progn (princ "\nOCMEMA WARN: distR>L, clamp a L") (setq distR l_total_cm)))
          (if (and (numberp distL) (<= distL 20.0)) (setq distL 0.0))
          (if (and (numberp distR) (<= (- l_total_cm distR) 20.0)) (setq distR l_total_cm))
          (setq xLstar (ocmema:dist->x distLstar x_support0 scaleX)) (setq xRstar (ocmema:dist->x distRstar x_support0 scaleX))
          (setq x_real_L (ocmema:dist->x distL x_support0 scaleX))
          (setq x_real_R (ocmema:dist->x distR x_support0 scaleX))
          (setq xL x_real_L) (setq xR x_real_R)
          (princ (strcat "\nOCMEMA DBG: face=TOP zone#" (itoa zoneIdx) " dist*=(" (rtos distLstar 2 3) "," (rtos distRstar 2 3) ") Ld_cm=" (rtos Ld_cm 2 3) " dist=(" (rtos distL 2 3) "," (rtos distR 2 3) ")"))
          (princ (strcat "\nOCMEMA DBG: face=TOP zone#" (itoa zoneIdx) " x*=(" (rtos xLstar 2 4) "," (rtos xRstar 2 4) ") x=(" (rtos xL 2 4) "," (rtos xR 2 4) ")"))
          (setq x_baston_ini x_real_L) (setq x_baston_fin x_real_R)
          (setq visExtraL 0.0) (setq visExtraR 0.0)
          (if (and (numberp distL) (= distL 0.0)) (setq visExtraL 0.25))
          (if (and (numberp distR) (= distR l_total_cm)) (setq visExtraR 0.25))
          (setq x_draw_L (- x_baston_ini visExtraL))
          (setq x_draw_R (+ x_baston_fin visExtraR))
          (setq deltaL (- x_real_L x_draw_L)) (setq deltaR (- x_draw_R x_real_R))
          (princ (strcat "\nOCMEMA DBG: baston face=TOP dist_real_cm=(" (rtos distL 2 3) "," (rtos distR 2 3) ") L_real_cm=" (rtos l_total_cm 2 3)))
          (princ (strcat "\nOCMEMA DBG: x_real=(" (rtos x_real_L 2 4) "," (rtos x_real_R 2 4) ") x_draw=(" (rtos x_draw_L 2 4) "," (rtos x_draw_R 2 4) ") extra=(" (rtos visExtraL 2 2) "," (rtos visExtraR 2 2) ")"))
          (princ (strcat "\nOCMEMA DBG: len_from_dist=" (rtos (/ (- distR distL) 100.0) 2 2) "m"))
          (princ (strcat "\nOCMEMA DBG: extra_check face=TOP dist=(" (rtos distL 2 3) ".." (rtos distR 2 3) ") L_real_cm=" (rtos l_total_cm 2 3) " deltaL=" (rtos deltaL 2 3) " deltaR=" (rtos deltaR 2 3)))
          (if (= distL 0.0)
            (princ (strcat "\nOCMEMA DBG: assert extraL=" (rtos (abs (- (- x_real_L x_draw_L) 0.25)) 2 3)))
            (princ (strcat "\nOCMEMA DBG: assert extraL=" (rtos (abs (- x_real_L x_draw_L)) 2 3)))
          )
          (if (= distR l_total_cm)
            (princ (strcat "\nOCMEMA DBG: assert extraR=" (rtos (abs (- (- x_draw_R x_real_R) 0.25)) 2 3)))
            (princ (strcat "\nOCMEMA DBG: assert extraR=" (rtos (abs (- x_draw_R x_real_R)) 2 3)))
          )
          (setq x_baston_ini x_draw_L) (setq x_baston_fin x_draw_R)
          (setq clampL (- x_support0 visExtraL))
          (setq clampR (+ x_supportL visExtraR))
          (if (< x_baston_ini clampL) (setq x_baston_ini clampL))
          (if (> x_baston_fin clampR) (setq x_baston_fin clampR))
                (command "_.PLINE" (list x_baston_ini (- yTop 0.45)) (list x_baston_ini (- yTop 0.15)) (list x_baston_fin (- yTop 0.15)) (list x_baston_fin (- yTop 0.45)) "") (command "_.CHPROP" (entlast) "" "Color" 5 "") (command "_.FILLET" "P" (entlast))
                (if (> distL 0.0)
                  (progn
                    (setq axis_near_start (get-closest-axis x_real_L axisXList))
                    (if axis_near_start (command "_.DIMLINEAR" (list axis_near_start (+ yOrigin h_draw)) (list x_real_L (+ yOrigin h_draw)) (list (/ (+ axis_near_start x_real_L) 2.0) (+ yOrigin h_draw 0.4))))
                  )
                )
                (if (< distR l_total_cm)
                  (progn
                    (setq axis_near_end (get-closest-axis x_real_R axisXList))
                    (if axis_near_end (command "_.DIMLINEAR" (list x_real_R (+ yOrigin h_draw)) (list axis_near_end (+ yOrigin h_draw)) (list (/ (+ x_real_R axis_near_end) 2.0) (+ yOrigin h_draw 0.4))))
                  )
                )
                (princ (strcat "\nBaston Sup Req: " (rtos deficit 2 2) " cm2. Long: " (rtos (/ (- distR distL) 100.0) 2 2) "m"))
                (setq areaBastOne (obtener-area-varilla strVarBast))
                (if (> areaBastOne 0.0) (progn (setq qtyBastRec (fix (+ (/ deficit areaBastOne) 0.9999))) (princ (strcat " Sugerido: " (itoa qtyBastRec))) (setq numBast (getint "\nCantidad definitiva: ")) (if (null numBast) (setq numBast qtyBastRec))) (setq numBast 1))
                (dibujar-leader-blindado (list (/ (+ x_baston_ini x_baston_fin) 2.0) (- yTop 0.15)) (strcat (itoa numBast) "#" strVarBast) T nil)
                (setq bastonesSupList (append bastonesSupList (list (list strVarBast numBast))))
       )
    )
    (princ (strcat "\n>>> Acero base cubre demanda Sup."))
  )

  ;; 6. ESTRIBOS (CORTANTE)
  (princ "\n--- ESTRIBOS ---")
  (setq d_eff (- h_cm 3.0)) (setq limitEstribos (max 20.0 (/ d_eff 2.0)))
  (setq yTextEstribos (- yOrigin 1.6))
  (command "_.TEXT" "_J" "_ML" (list xOrigin yTextEstribos) 0.25 0 "E#3") (command "_.CHPROP" (entlast) "" "Color" 3 "")
  (setq numZonesEstribos (getint "\nNumero de zonas de estribos (1 para uniforme): ")) (if (null numZonesEstribos) (setq numZonesEstribos 1))
  (setq currentDist 0.0) (setq i 1)
  (repeat numZonesEstribos
     (if (= numZonesEstribos 1) (setq lenZoneEst l_total_m) (setq lenZoneEst (getreal (strcat "\nLongitud Zona " (itoa i) " (m): "))))
     (setq s_estribo (getreal (strcat "Separacion Zona " (itoa i) " (cm): ")))
     (if (> s_estribo limitEstribos) (princ (strcat "\n** AVISO: Sep " (rtos s_estribo 2 0) " > Limite " (rtos limitEstribos 2 0) " **")))
     (setq qtyEstribos (fix (+ (/ (* lenZoneEst 100.0) s_estribo) 0.99)))
     (if (= i 1) (setq qtyEstribos (1+ qtyEstribos)))
     (setq txtEstribo (strcat (itoa qtyEstribos) "@" (rtos s_estribo 2 0)))
     (setq pTextEst (list (+ (car p1) 0.5 currentDist (/ lenZoneEst 2.0)) yTextEstribos))
     (command "_.TEXT" "_J" "_MC" pTextEst 0.15 0 txtEstribo) (command "_.CHPROP" (entlast) "" "Color" 8 "")
     (setq currentDist (+ currentDist lenZoneEst)) (setq i (1+ i))
  )

  ;; 7. CONTRAFLECHA (Correccion Y = -0.65)
  (initget "Si No") (setq addCamber (getkword "\nAgregar contraflecha? [Si/No] <No>: "))
  (if (= addCamber "Si")
     (progn (setq numCamber (getint "\nCuantas contraflechas?: "))
        (repeat numCamber
           (initget "Centro Distancia") (setq locCamber (getkword "\nUbicacion? [Centro de Claro / Distancia]: "))
           (if (= locCamber "Centro")
              (progn (setq i (getint "Numero de claro (1, 2...): ")) (setq xCamber (/ (+ (nth (1- i) axisXList) (nth i axisXList)) 2.0)))
              (setq xCamber (+ (car p1) 0.5 (getreal "Distancia desde origen (m): ")))
           )
           (setq strCamber (getstring "\nValor Contraflecha (ej. 1.5): "))
           (setq yCamber (- yOrigin 0.65)) 
           
           (setq deltaW 0.16) (setq gap 0.05) (setq textW (* (strlen (strcat "=" strCamber "cm")) 0.12))
           (setq totalW (+ deltaW gap textW))
           (setq xDelta (- xCamber (/ totalW 2.0)))
           
           (command "_.PLINE" (list xDelta yCamber) (list (- xDelta 0.08) (- yCamber 0.15)) (list (+ xDelta 0.08) (- yCamber 0.15)) "C")
           (command "_.CHPROP" (entlast) "" "Color" 40 "")
           (command "_.TEXT" "_J" "_ML" (list (+ xDelta 0.08 gap) (- yCamber 0.075)) 0.15 0 (strcat "=" strCamber "cm")) (command "_.CHPROP" (entlast) "" "Color" 40 "")
        )
     )
  )

  ;; 8. SECCION TRANSVERSAL
  (princ "\n--- SECCION TRANSVERSAL ---")
  (setq ptSectionOrigin (list (+ (car p2) 1.5) yOrigin)) 
  (setq xSec (car ptSectionOrigin) ySec (cadr ptSectionOrigin))
  (setq b_draw (* (/ b_cm 100.0) 7.0)) (setq h_draw_sec (* (/ h_cm 100.0) 7.0))
  
  (command "_.RECTANG" "_F" 0 ptSectionOrigin (list (+ xSec b_draw) (+ ySec h_draw_sec))) (command "_.CHPROP" (entlast) "" "Color" 7 "")

  ;; Losa (Zig Zag Recto)
  (initget "Si No") (setq hasLosa (getkword "\nLleva Losa? [Si/No] <No>: "))
  (if (= hasLosa "Si")
    (progn
      (initget "Izq Der Ambos") (setq typeLosa (getkword "Lado? [Izq/Der/Ambos]: "))
      (setq capaCompresion (* (/ (getreal "Capa Compresion (cm): ") 100.0) 7.0))
      (setq h_losa (* (/ (getreal "Altura Total Losa (cm): ") 100.0) 7.0))
      (setq alignLosa "Arriba")
      (if (not (equal h_draw_sec h_losa 0.01)) (progn (initget "Arriba Abajo Centro") (setq alignLosa (getkword "Alineacion Losa? [Arriba/Abajo/Centro]: "))))
      (setq yLosaStart (+ ySec h_draw_sec))
      (if (= alignLosa "Abajo") (setq yLosaStart (+ ySec h_losa)))
      (if (= alignLosa "Centro") (setq yLosaStart (+ ySec (/ h_draw_sec 2.0) (/ h_losa 2.0))))
      
      (defun draw-break-line (xStart yTop hLosa hCapa isLeft / dir xEnd yCenter ptsHatch)
         (setq dir (if isLeft -1.0 1.0)) (setq xEnd (+ xStart (* 0.5 dir)))
         (command "_.RECTANG" (list xStart yTop) (list xEnd (- yTop hCapa))) (command "_.CHPROP" (entlast) "" "Color" 7 "")
         
         (setq yCenter (- yTop (/ hLosa 2.0)))
         (setq ptsHatch (list (list xStart (- yTop hCapa)) (list xEnd (- yTop hCapa)) 
               (list xEnd (+ yCenter 0.075)) (list (- xEnd (* 0.2 dir)) (+ yCenter 0.075))
               (list (- xEnd (* 0.2 dir)) yCenter) (list (+ xEnd (* 0.2 dir)) yCenter)
               (list (+ xEnd (* 0.2 dir)) (- yCenter 0.075)) (list xEnd (- yCenter 0.075))
               (list xEnd (- yTop hLosa)) (list xStart (- yTop hLosa))))
         (command "_.PLINE") (foreach p ptsHatch (command p)) (command "_C")
         (command "_.CHPROP" (entlast) "" "Color" 8 "") (command "_.HATCH" "ANSI31" 0.035 0 (entlast) "") (command "_.CHPROP" (entlast) "" "Color" 8 "")
         
         (command "_.PLINE" (list xEnd (+ yTop 0.2)) (list xEnd (+ yCenter 0.075)) (list (- xEnd (* 0.2 dir)) (+ yCenter 0.075))
            (list (- xEnd (* 0.2 dir)) yCenter) (list (+ xEnd (* 0.2 dir)) yCenter) (list (+ xEnd (* 0.2 dir)) (- yCenter 0.075))
            (list xEnd (- yCenter 0.075)) (list xEnd (- yTop hLosa 0.2)) "") (command "_.CHPROP" (entlast) "" "Color" 7 "")
      )
      (if (or (= typeLosa "Izq") (= typeLosa "Ambos")) (draw-break-line xSec yLosaStart h_losa capaCompresion T))
      (if (or (= typeLosa "Der") (= typeLosa "Ambos")) (draw-break-line (+ xSec b_draw) yLosaStart h_losa capaCompresion nil))
    )
  )

  ;; Estribo (Fillet 0.025 fijo)
  (setq radFillet 0.025)
  (setq rec_draw 0.175)
  (setq p1_st (list (+ xSec rec_draw) (+ ySec rec_draw)))
  (setq p2_st (list (- (+ xSec b_draw) rec_draw) (- (+ ySec h_draw_sec) rec_draw)))
  (command "_.RECTANG" "_F" radFillet p1_st p2_st) (command "_.CHPROP" (entlast) "" "Color" 3 "")
  (command "_.RECTANG" "_F" 0 (list 0 0) (list 0 0)) (command "_.ERASE" (entlast) "")

  ;; Ganchos 135 (OFFSET CORREGIDO 1.1*RadioVARILLA)
  (setq rBarTop (/ (* (/ (obtener-diametro-real strVarBaseTop) 100.0) 7.0) 2.0))
  (setq xStirrupLeft (car p1_st))
  (setq yStirrupTop (cadr p2_st))
  (setq offsetHookFactor (* rBarTop 1.1)) ;; 1.1 * Radio de la Varilla (NO filete)
  
  ;; H1 (Top leg): Start shifted Right by (rBar + offset)
  (setq centerBarX (+ xStirrupLeft rBarTop))
  (setq pH1 (list (+ centerBarX offsetHookFactor) yStirrupTop))
  (command "_.LINE" pH1 (polar pH1 (* 315.0 (/ pi 180.0)) 0.30) "") (command "_.CHPROP" (entlast) "" "Color" 3 "")
  
  ;; H2 (Left leg): Start shifted Down by (rBar + offset)
  (setq centerBarY (- yStirrupTop rBarTop))
  (setq pH2 (list xStirrupLeft (- centerBarY offsetHookFactor)))
  (command "_.LINE" pH2 (polar pH2 (* 315.0 (/ pi 180.0)) 0.30) "") (command "_.CHPROP" (entlast) "" "Color" 3 "")

  ;; LOGICA ACERO
  (defun get-critical-bast (bastList / critVar critNum maxD)
     (setq critVar nil critNum 0 maxD 0.0)
     (foreach b bastList
        (setq d (obtener-diametro-real (car b)))
        (if (> d maxD) (progn (setq maxD d) (setq critVar (car b)) (setq critNum (cadr b)))
           (if (and (= d maxD) (> (cadr b) critNum)) (setq critNum (cadr b)))))
     (list critVar critNum)
  )
  (setq critBastInf (get-critical-bast bastonesInfList))
  (setq critBastSup (get-critical-bast bastonesSupList))

  (defun ocmema--sort-num (lst / out x)
    (setq out '())
    (foreach x lst
      (setq out
        (vl-sort (append out (list x)) '(lambda (a b) (< a b)))
      )
    )
    out
  )

  (defun ocmema--segment-pos (a b n / gap j out)
    (setq out '())
    (if (<= n 0)
      out
      (if (= n 1)
        (list (/ (+ a b) 2.0))
        (progn
          (setq gap (/ (- b a) (1+ n)))
          (setq j 1)
          (repeat n
            (setq out (append out (list (+ a (* gap j)))))
            (setq j (1+ j))
          )
          out
        )
      )
    )
  )

  (defun ocmema--as-list (v)
    (cond
      ((null v) '())
      ((listp v) v)
      (T (list v))
    )
  )

  (defun ocmema--count-near (lst target tol / count v)
    (setq count 0)
    (foreach v lst
      (if (<= (abs (- v target)) tol)
        (setq count (1+ count))
      )
    )
    count
  )

  (defun ocmema--draw-xlist (xlist y / pts p pt)
    (setq pts (ocmema--as-list xlist))
    (foreach p pts
      (if (and (listp p) (>= (length p) 2) (numberp (car p)) (numberp (cadr p)))
        (setq pt (list (car p) (cadr p)))
        (setq pt (list p y))
      )
      (command "_.DONUT" 0.0 diamBase pt "")
      (command "_.CHPROP" (entlast) "" "Color" 5 "")
    )
  )

  (defun ocmema--clamp-int (v lo hi)
    (cond
      ((null v) lo)
      ((< v lo) lo)
      ((> v hi) hi)
      (T v)
    )
  )

  (defun ocmema--ask-bast-orillas (bastNum levelsIzq levelsDer maxLevels isTop / nO capIzq capDer capTot prompt)
    (setq prompt (strcat "\nBastones (" (if isTop "SUP" "INF") "): tienes " (itoa bastNum) ". Cuantos van en orillas (Total) (0-" (itoa bastNum) ")?: "))
    (setq capIzq (max 0 (+ 1 (- maxLevels levelsIzq))))
    (setq capDer (max 0 (+ 1 (- maxLevels levelsDer))))
    (setq capTot (+ capIzq capDer))
    (setq nO (ocmema--clamp-int (getint prompt) 0 bastNum))
    (while (> nO capTot)
      (princ (strcat "\nNo caben tantos bastones en orillas con los niveles actuales. Max posible = " (itoa capTot) "."))
      (setq nO (ocmema--clamp-int (getint prompt) 0 bastNum))
    )
    (list nO capTot)
  )

  (defun process-layer-steel (baseNum baseVar bastNum bastVar isTop / diamBase diamBast yStart dir layoutMode eps maxLevels xL xR xC totalBarsBase w gap i positions positionsPts nOBase nInner levelsIzq levelsDer levelsCen askRes nO nC cx cy ly sideName)
     (setq diamBase (* (/ (obtener-diametro-real baseVar) 100.0) 7.0))
     (setq diamBast 0.0)
     (if bastVar (setq diamBast (* (/ (obtener-diametro-real bastVar) 100.0) 7.0)))
     (setq yStart (if isTop (- (cadr p2_st) (/ diamBase 2.0)) (+ (cadr p1_st) (/ diamBase 2.0))))
     (setq dir (if isTop -1.0 1.0))
     (setq eps 1e-4)
     (setq maxLevels 2)
     (initget "Orillas Largo")
     (setq layoutMode (getkword (strcat "\nAcomodo " (if isTop "SUP" "INF") " (Base:" (itoa baseNum) " Bast:" (itoa bastNum) ")? [Orillas/Largo]: ")))

     (setq xL (+ (car p1_st) (/ diamBase 2.0)))
     (setq xR (- (car p2_st) (/ diamBase 2.0)))
     (setq xC (/ (+ xL xR) 2.0))

     (if (= layoutMode "Largo")
       (progn
         (setq totalBarsBase (if (and (numberp baseNum) (> baseNum 0)) baseNum 1))
         (setq w (- xR xL))
         (setq gap (if (> totalBarsBase 1) (/ w (1- totalBarsBase)) 0.0))
         (setq i 0 positions nil)
         (repeat totalBarsBase
           (setq positions (append positions (list (+ xL (* i gap)))))
           (setq i (1+ i))
         )
         (setq positions (ocmema--as-list positions))
         (setq positions (ocmema--sort-num positions))
         (ocmema--draw-xlist positions yStart)
         (if (> bastNum 0)
           (progn
             (setq levelsIzq (ocmema--count-near positions xL eps))
             (setq levelsDer (ocmema--count-near positions xR eps))
             (setq levelsCen (ocmema--count-near positions xC eps))
             (setq askRes (ocmema--ask-bast-orillas bastNum levelsIzq levelsDer maxLevels isTop))
             (setq nO (car askRes))
             (setq nC (- bastNum nO))
             (setq i 0)
             (repeat nO
               (if (<= levelsIzq levelsDer)
                 (progn (setq cx xL) (setq ly levelsIzq) (setq levelsIzq (1+ levelsIzq)))
                 (progn (setq cx xR) (setq ly levelsDer) (setq levelsDer (1+ levelsDer)))
               )
               (setq cy (+ yStart (* ly diamBast dir)))
               (command "_.DONUT" 0.0 diamBast (list cx cy) "")
               (command "_.CHPROP" (entlast) "" "Color" 5 "")
               (setq i (1+ i))
             )
             (if (> nC 0)
               (progn
                 (setq i 0)
                 (repeat nC
                   (setq cx xC)
                   (setq ly levelsCen)
                   (setq levelsCen (1+ levelsCen))
                   (setq cy (+ yStart (* ly diamBast dir)))
                   (command "_.DONUT" 0.0 diamBast (list cx cy) "")
                   (command "_.CHPROP" (entlast) "" "Color" 5 "")
                   (setq i (1+ i))
                 )
               )
             )
           )
         )
       )
       (progn
         (setq levelsIzq 0 levelsDer 0 levelsCen 0)
         (setq nOBase baseNum)
         (if (> baseNum 2)
           (progn
             (setq nOBase (getint "\nCuantas barras van en orillas (Total)?: "))
             (if (or (null nOBase) (< nOBase 2)) (setq nOBase 2))
             (if (> nOBase baseNum) (setq nOBase baseNum))
           )
         )
         (setq positions nil)
         (setq positionsPts nil)
         (if (>= baseNum 2)
           (progn
             (setq positions (append positions (list xL xR)))
             (setq positionsPts (append positionsPts (list (list xL yStart) (list xR yStart))))
             (setq levelsIzq 1 levelsDer 1)
           )
           (progn
             (setq positions (append positions (list xC)))
             (setq positionsPts (append positionsPts (list (list xC yStart))))
           )
         )
         (if (> nOBase 2)
           (progn
             (setq i 0)
             (repeat (fix (/ (+ (- nOBase 2) 1) 2))
               (setq positions (append positions (list xL)))
               (setq positionsPts (append positionsPts (list (list xL (+ yStart (* levelsIzq diamBase dir))))))
               (setq levelsIzq (1+ levelsIzq))
               (setq i (1+ i))
             )
             (setq i 0)
             (repeat (fix (/ (- nOBase 2) 2))
               (setq positions (append positions (list xR)))
               (setq positionsPts (append positionsPts (list (list xR (+ yStart (* levelsDer diamBase dir))))))
               (setq levelsDer (1+ levelsDer))
               (setq i (1+ i))
             )
           )
         )
         (setq nInner (- baseNum nOBase))
         (if (> nInner 0)
           (progn
             (if (= nInner 1)
               (progn
                 (setq positions (append positions (list xC)))
                 (setq positionsPts (append positionsPts (list (list xC yStart))))
               )
               (foreach cx (ocmema--segment-pos xL xR nInner)
                 (setq positions (append positions (list cx)))
                 (setq positionsPts (append positionsPts (list (list cx yStart))))
               )
             )
           )
         )
         (setq positions (ocmema--sort-num positions))
         (ocmema--draw-xlist positionsPts yStart)
         (if (> bastNum 0)
           (progn
             (setq levelsIzq (ocmema--count-near positions xL eps))
             (setq levelsDer (ocmema--count-near positions xR eps))
             (setq levelsCen (ocmema--count-near positions xC eps))
             (setq askRes (ocmema--ask-bast-orillas bastNum levelsIzq levelsDer maxLevels isTop))
             (setq nO (car askRes))
             (setq nC (- bastNum nO))
             (setq i 0)
             (repeat nO
               (if (<= levelsIzq levelsDer)
                 (progn (setq sideName "Izq") (setq cx xL) (setq ly levelsIzq) (setq levelsIzq (1+ levelsIzq)))
                 (progn (setq sideName "Der") (setq cx xR) (setq ly levelsDer) (setq levelsDer (1+ levelsDer)))
               )
               (setq cy (+ yStart (* ly diamBast dir)))
               (command "_.DONUT" 0.0 diamBast (list cx cy) "")
               (command "_.CHPROP" (entlast) "" "Color" 5 "")
               (setq i (1+ i))
             )
             (if (> nC 0)
               (progn
                 (setq i 0)
                 (repeat nC
                   (setq cx xC)
                   (setq ly levelsCen)
                   (setq levelsCen (1+ levelsCen))
                   (setq cy (+ yStart (* ly diamBast dir)))
                   (command "_.DONUT" 0.0 diamBast (list cx cy) "")
                   (command "_.CHPROP" (entlast) "" "Color" 5 "")
                   (setq i (1+ i))
                 )
               )
             )
           )
         )
       )
     )
  )

  (defun ocmema--draw-temp-bars-const (/ pairs k frac ySecBar yLongBar xLeftBar xRightBar diamTemp xLdraw xRdraw yLabel lastYLong)
    (setq pairs (fix (/ h_cm 40.0)))
    (if (and (numberp pairs) (>= pairs 1))
      (progn
        (setq diamTemp (* (/ (obtener-diametro-real "3") 100.0) 7.0))
        (setq xLeftBar (+ (car p1_st) (/ diamTemp 2.0)))
        (setq xRightBar (- (car p2_st) (/ diamTemp 2.0)))
        (setq xLdraw (+ (car p1) 0.15))
        (setq xRdraw (- (car p2) 0.15))
        (setq k 1)
        (setq lastYLong nil)
        (repeat pairs
          (setq frac (/ (float k) (+ pairs 1.0)))
          (setq ySecBar (+ (cadr p1_st) (* frac (- (cadr p2_st) (cadr p1_st)))))
          (setq yLongBar (+ yOrigin 0.15 (* frac (- h_draw 0.30))))
          (setq lastYLong yLongBar)
          (command "_.DONUT" 0.0 diamTemp (list xLeftBar ySecBar) "")
          (command "_.CHPROP" (entlast) "" "Color" 5 "")
          (command "_.DONUT" 0.0 diamTemp (list xRightBar ySecBar) "")
          (command "_.CHPROP" (entlast) "" "Color" 5 "")
          (command "_.PLINE" (list xLdraw (+ yLongBar 0.10)) (list xLdraw yLongBar) (list xRdraw yLongBar) (list xRdraw (+ yLongBar 0.10)) "")
          (command "_.CHPROP" (entlast) "" "Color" 5 "")
          (command "_.FILLET" "P" (entlast))
          (setq k (1+ k))
        )
        (if lastYLong
          (progn
            (setq yLabel (+ yOrigin 0.15 (* (/ (+ 1.0 pairs) 2.0) (/ (- h_draw 0.30) (+ pairs 1.0)))))
            (dibujar-leader-blindado (list (/ (+ xLdraw xRdraw) 2.0) yLabel) (strcat (itoa (* 2 pairs)) "#3") nil nil)
          )
        )
      )
    )
  )
  
  (process-layer-steel numBaseBot strVarBaseBot (cadr critBastInf) (car critBastInf) nil)
  (process-layer-steel numBaseTop strVarBaseTop (cadr critBastSup) (car critBastSup) T)
  (ocmema--draw-temp-bars-const)

  (setvar "DIMASZ" old_dimasz) (setvar "DIMCLRD" old_dimclrd) (setvar "DIMTXT" old_dimtxt) (setvar "DIMCLRT" old_dimclrt) (setvar "DIMSCALE" old_dimscale) (setvar "OSMODE" oldOsnap)
  (princ "\nDibujo de Trabe completado.")
  (princ)
)

(defun c:DIBUJAR_TRABE_SIMPLE () (ocmema:beam:const-armar-from-anl nil))
(defun c:DIBUJAR_TRABE_V13 () (ocmema:beam:const-armar-from-anl nil))
